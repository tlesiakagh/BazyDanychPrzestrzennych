FME workspace cw4.fmw

Parameters:
- SourceDataset_POSTGIS_RASTER =

Readers:
- POSTGIS_RASTER_1: POSTGIS_RASTER from $(SourceDataset_POSTGIS_RASTER)

exports (reader POSTGIS_RASTER_1)
    -> SQLExecutor [INITIATOR]
SQLExecutor
    ATTR_IGNORE_NULLS = No
    COMBINE_ATTRS = Keep Result Attributes if Conflict
    COMBINE_GEOM = Result Geometry Only
    DATASET = cw9
    FORMAT = POSTGIS_RASTER
    POSTGIS_RASTER_NAMED_CONNECTION = cw9
    POSTGIS_RASTER_QUERY_FEATURE_TYPES_FOR_MERGE_FILTERS = Yes
    POSTGIS_RASTER_READER_META_ATTRIBUTES = fme_basename
    POSTGIS_RASTER_READ_TIME_WITH_TIMEZONE = Yes
    POSTGIS_RASTER_SCHEMAS_FOR_TABLE_LISTING = public
    SQL_STATEMENT:
      SELECT ST_Union(rast) INTO exportsUnion
      FROM public.exports;
